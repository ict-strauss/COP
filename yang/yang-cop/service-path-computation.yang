module service-path-computation {

    yang-version 1;

    namespace "http://ict-strauss.eu/cop/service-path-computation";

    prefix s-path;

    import service-call {
		prefix sc;
	}

    organization "CTTC";

    revision "2015-05-30" {
        description
        "Service Path Computation module for STRAUSS";
    }



    grouping path_request{
        description "";
        
        leaf request-id{
            type string;
        }
        container aEnd{
            uses sc:endpoint;
        }
        container zEnd{
            uses sc:endpoint;
        }
        container traffic_parameters{
            description "TrafficParam covers service specific traffic attributes";
            uses sc:traffic_params;
        }

    }
    
    grouping path_reply{
        description "";
        leaf reply-id{
            type string;
        }
        container path{
            uses sc:path-type;
        }
    }

    rpc path_computation{
        input {
            uses path_request;
        }
        output{
            uses path_reply;
        }
        
    }
}

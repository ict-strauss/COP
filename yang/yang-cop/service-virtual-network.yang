module service-virtual-network {

    yang-version 1;

    namespace "http://ict-strauss.eu/cop/service-virtual-network";

    prefix s-vnet;
    
    import service-topology{
    	prefix s-topo;
    }

    organization "CTTC";

    description "YANG version of the Common Orchestration Protocol (COP).";

    revision "2015-06-23" {
        description
        "Service Virtual Network module for STRAUSS";
    }

    typedef virtual-network-ref {
        type leafref {
            path "/virtual_networks/virtual_network/virtual_network_id";
        }
        description
            "A type for a virtual network instance.";
    }


    grouping virtual_network{
        leaf virtual_network_id{
            type string;
        }
        leaf tenant_ip{
            type string;
        }
        list vNodes{
	    config false;
	    key "vNode_id";
            uses vNode;
        }
        list vEdges{
	    config false;
            key "vEdge_id";
            uses vEdge;
        }
    }

    grouping vEdge_end{
        leaf vEdge_end_id{
            type string;
        }
        container pNode{
            uses s-topo:node;
        }
        container pEdgeEnd{
            uses s-topo:edge_end;
        }
    }

    grouping vNode{
        leaf vNode_id{
            type string;
        }
        list vEdge_ends{
            key "vEdge_end_id";
            uses vEdge_end;
        }
    }

    grouping vEdge{
        leaf vEdge_id{
            type string;
        }
        
        container source{
	    config false;
            uses vNode;
        }
        container target{
	    config false;
            uses vNode;
        }
        container local_ifid{
	    config false;
            uses vEdge_end;
        }
        container remote_ifid{
	    config false;
            uses vEdge_end;
        }
    }

    container virtual_networks{
        list virtual_network{
            key "virtual_network_id";
            uses virtual_network;
        }
    }

}
